module Cluster {
  
  namespace "http://rakuten.com/RCP/network";

  prefix "Cluster";

  import Base {
    prefix "Base";
  }

  Base:source "RCP-Base";
  Base:version "1.0";

  Base:baseType "LogicalResource" {
     Base:source "RCP-Base";
     Base:version "1.0";
  }

  organization "Rakuten";
  contact "";
  description "Cluster generated from puml";

  revision 2020-08-20 {
    description "Initial Version";
    reference "";
  }

  container attributes {
    description "Cluster Attributes";
    }

    container relationships {
    description "Relationship definitions";

    }
  }
