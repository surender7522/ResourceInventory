module Fabric {
  
  namespace "http://rakuten.com/RCP/network";

  prefix "Fabric";

  import Base {
    prefix "Base";
  }

  Base:source "RCP-Base";
  Base:version "1.0";

  Base:baseType "Connection" {
     Base:source "RCP-Base";
     Base:version "1.0";
  }

  organization "Rakuten";
  contact "";
  description "Fabric generated from puml";

  revision 2020-08-20 {
    description "Initial Version";
    reference "";
  }

  container attributes {
    description "Fabric Attributes";
    }

    container relationships {
    description "Relationship definitions";

    }
  }
