module VLANInterface {
  
  namespace "http://rakuten.com/RCP/network";

  prefix "VLANInterface";

  import Base {
    prefix "Base";
  }

  Base:source "RCP-Base";
  Base:version "1.0";

  Base:baseType "LogicalInterface" {
     Base:source "RCP-Base";
     Base:version "1.0";
  }

  organization "Rakuten";
  contact "";
  description "VLANInterface generated from puml";

  revision 2020-08-20 {
    description "Initial Version";
    reference "";
  }

  container attributes {
    description "VLANInterface Attributes";
    }

    container relationships {
    description "Relationship definitions";

    }
  }
