module CNFC {
  
  namespace "http://rakuten.com/RCP/network";

  prefix "CNFC";

  import Base {
    prefix "Base";
  }

  Base:source "RCP-Base";
  Base:version "1.0";

  Base:baseType "VNFC" {
     Base:source "RCP-Base";
     Base:version "1.0";
  }

  organization "Rakuten";
  contact "";
  description "CNFC generated from puml";

  revision 2020-08-20 {
    description "Initial Version";
    reference "";
  }

  container attributes {
    description "CNFC Attributes";
    leaf cnfcInstanceId {
      type string;
      description "";
      mandatory  "false";
      default "";
    }
    leaf cnfcIPPool {
      type string;
      description "";
      mandatory  "false";
      default "";
    }
    leaf cnfcResourcePool {
      type string;
      description "";
      mandatory  "false";
      default "";
    }
    leaf cnfcBundleId {
      type string;
      description "";
      mandatory  "false";
      default "";
    }
    leaf cnfcLabels {
      type string;
      description "";
      mandatory  "false";
      default "";
    }
    }

    container relationships {
    description "Relationship definitions";
    leaf runson_0 {
      type Base:relatedType { 
        Base:relationship "runson";
        Base:relType "K8_POD";
        Base:source "RCP-Base";
        Base:version "1.0";
      }
    }
    leaf has_0 {
      type Base:relatedType { 
        Base:relationship "has";
        Base:relType "SideCar";
        Base:source "RCP-Base";
        Base:version "1.0";
      }
    }

    }
  }
