module Router {
  
  namespace "http://rakuten.com/RCP/network";

  prefix "Router";

  import Base {
    prefix "Base";
  }

  Base:source "RCP-Base";
  Base:version "1.0";

  Base:baseType "NetworkElement" {
     Base:source "RCP-Base";
     Base:version "1.0";
  }

  organization "Rakuten";
  contact "";
  description "Router generated from puml";

  revision 2020-08-20 {
    description "Initial Version";
    reference "";
  }

  container attributes {
    description "Router Attributes";
    }

    container relationships {
    description "Relationship definitions";

    }
  }
