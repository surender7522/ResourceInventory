module Package {
  
  namespace "http://rakuten.com/RCP/network";

  prefix "Package";

  import Base {
    prefix "Base";
  }

  Base:source "RCP-Base";
  Base:version "1.0";

  Base:baseType "GenericEntity" {
     Base:source "RCP-Base";
     Base:version "1.0";
  }

  organization "Rakuten";
  contact "";
  description "Package generated from puml";

  revision 2020-08-20 {
    description "Initial Version";
    reference "";
  }

  container attributes {
    description "Package Attributes";
    leaf pkgid {
      type string;
      description "";
      mandatory  "false";
      default "";
    }
    leaf nf_package_version {
      type string;
      description "";
      mandatory  "false";
      default "";
    }
    }

    container relationships {
    description "Relationship definitions";
    leaf has_0 {
      type Base:relatedType { 
        Base:relationship "has";
        Base:relType "Bundle";
        Base:source "RCP-Base";
        Base:version "1.0";
      }
    }

    }
  }
