module LogicalInterface {
  
  namespace "http://rakuten.com/RCP/network";

  prefix "LogicalInterface";

  import Base {
    prefix "Base";
  }

  Base:source "RCP-Base";
  Base:version "1.0";

  Base:baseType "Entity" {
     Base:source "RCP-Base";
     Base:version "1.0";
  }

  organization "Rakuten";
  contact "";
  description "LogicalInterface generated from puml";

  revision 2020-08-20 {
    description "Initial Version";
    reference "";
  }

  container attributes {
    description "LogicalInterface Attributes";
    leaf lifpName {
      type string;
      description "";
      mandatory  "false";
      default "";
    }
    }

    container relationships {
    description "Relationship definitions";
    leaf contains_0 {
      type Base:relatedType { 
        Base:relationship "contains";
        Base:relType "LogicalInterface";
        Base:source "RCP-Base";
        Base:version "1.0";
      }
    }

    }
  }
