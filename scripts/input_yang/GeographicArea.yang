module GeographicArea {
  
  namespace "http://rakuten.com/RCP/network";

  prefix "GeographicArea";

  import Base {
    prefix "Base";
  }

  Base:source "RCP-Base";
  Base:version "1.0";

  Base:baseType "Location" {
     Base:source "RCP-Base";
     Base:version "1.0";
  }

  organization "Rakuten";
  contact "";
  description "GeographicArea generated from puml";

  revision 2020-08-20 {
    description "Initial Version";
    reference "";
  }

  container attributes {
    description "GeographicArea Attributes";
    leaf geaCode {
      type string;
      description "";
      mandatory  "false";
      default "";
    }
    }

    container relationships {
    description "Relationship definitions";
    leaf contains_0 {
      type Base:relatedType { 
        Base:relationship "contains";
        Base:relType "GeographicArea";
        Base:source "RCP-Base";
        Base:version "1.0";
      }
    }
    leaf contains_1 {
      type Base:relatedType { 
        Base:relationship "contains";
        Base:relType "GeoLocation";
        Base:source "RCP-Base";
        Base:version "1.0";
      }
    }

    }
  }
