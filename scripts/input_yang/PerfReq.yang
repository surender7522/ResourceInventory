module PerfReq {
  
  namespace "http://rakuten.com/RCP/network";

  prefix "PerfReq";

  import Base {
    prefix "Base";
  }

  Base:source "RCP-Base";
  Base:version "1.0";

  Base:baseType "GenericEntity" {
     Base:source "RCP-Base";
     Base:version "1.0";
  }

  organization "Rakuten";
  contact "";
  description "PerfReq generated from puml";

  revision 2020-08-20 {
    description "Initial Version";
    reference "";
  }

  container attributes {
    description "PerfReq Attributes";
    leaf preqExpDataRateDL {
      type int64;
      description "";
      mandatory  "false";
      default "";
    }
    leaf preqExpDataRateUL {
      type int64;
      description "";
      mandatory  "false";
      default "";
    }
    leaf preqAreaTrafficCapDL {
      type int64;
      description "";
      mandatory  "false";
      default "";
    }
    leaf preqAreaTrafficCapUL {
      type int64;
      description "";
      mandatory  "false";
      default "";
    }
    leaf preqOverallUserDensity {
      type int64;
      description "";
      mandatory  "false";
      default "";
    }
    leaf preqActivityFactor {
      type int64;
      description "";
      mandatory  "false";
      default "";
    }
    leaf preqCSAvailabilityTarget {
      type string;
      description "";
      mandatory  "false";
      default "";
    }
    leaf preqCSReliabilityMeanTime {
      type string;
      description "";
      mandatory  "false";
      default "";
    }
    leaf preqExpDataRate {
      type string;
      description "";
      mandatory  "false";
      default "";
    }
    leaf preqMsgSizeByte {
      type string;
      description "";
      mandatory  "false";
      default "";
    }
    leaf preqTransferIntervalTarget {
      type string;
      description "";
      mandatory  "false";
      default "";
    }
    leaf preqSurvivalTime {
      type string;
      description "";
      mandatory  "false";
      default "";
    }
    leaf preqUESpeed {
      type int64;
      description "";
      mandatory  "false";
      default "";
    }
    leaf preqCoverage {
      type string;
      description "";
      mandatory  "false";
      default "";
    }
    }

    container relationships {
    description "Relationship definitions";

    }
  }
