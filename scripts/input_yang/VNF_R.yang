module VNF_R {
  
  namespace "http://rakuten.com/RCP/network";

  prefix "VNF_R";

  import Base {
    prefix "Base";
  }

  Base:source "RCP-Base";
  Base:version "1.0";

  Base:baseType "VNF" {
     Base:source "RCP-Base";
     Base:version "1.0";
  }

  organization "Rakuten";
  contact "";
  description "VNF_R generated from puml";

  revision 2020-08-20 {
    description "Initial Version";
    reference "";
  }

  container attributes {
    description "VNF_R Attributes";
    }

    container relationships {
    description "Relationship definitions";
    leaf has_0 {
      type Base:relatedType { 
        Base:relationship "has";
        Base:relType "Bundle";
        Base:source "RCP-Base";
        Base:version "1.0";
      }
    }

    }
  }
