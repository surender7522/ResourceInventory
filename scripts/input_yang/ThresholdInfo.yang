module ThresholdInfo {
  
  namespace "http://rakuten.com/RCP/network";

  prefix "ThresholdInfo";

  import Base {
    prefix "Base";
  }

  Base:source "RCP-Base";
  Base:version "1.0";

  Base:baseType "GenericEntity" {
     Base:source "RCP-Base";
     Base:version "1.0";
  }

  organization "Rakuten";
  contact "";
  description "ThresholdInfo generated from puml";

  revision 2020-08-20 {
    description "Initial Version";
    reference "";
  }

  container attributes {
    description "ThresholdInfo Attributes";
    leaf thinfoThresholdLevel {
      type string;
      description "";
      mandatory  "false";
      default "";
    }
    leaf thinfoThresholdDirection {
      type string;
      description "";
      mandatory  "false";
      default "";
    }
    leaf thinfoThresholdValue {
      type string;
      description "";
      mandatory  "false";
      default "";
    }
    leaf thinfoHysteresis {
      type string;
      description "";
      mandatory  "false";
      default "";
    }
    }

    container relationships {
    description "Relationship definitions";

    }
  }
