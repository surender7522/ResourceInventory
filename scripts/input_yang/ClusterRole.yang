module ClusterRole {
  
  namespace "http://rakuten.com/RCP/network";

  prefix "ClusterRole";

  import Base {
    prefix "Base";
  }

  Base:source "RCP-Base";
  Base:version "1.0";

  Base:baseType "Role" {
     Base:source "RCP-Base";
     Base:version "1.0";
  }

  organization "Rakuten";
  contact "";
  description "ClusterRole generated from puml";

  revision 2020-08-20 {
    description "Initial Version";
    reference "";
  }

  container attributes {
    description "ClusterRole Attributes";
    leaf hostType {
      type string;
      description "";
      mandatory  "false";
      default "";
    }
    }

    container relationships {
    description "Relationship definitions";
    leaf has_0 {
      type Base:relatedType { 
        Base:relationship "has";
        Base:relType "Server";
        Base:source "RCP-Base";
        Base:version "1.0";
      }
    }

    }
  }
