module K8_Service {
  
  namespace "http://rakuten.com/RCP/network";

  prefix "K8_Service";

  import Base {
    prefix "Base";
  }

  Base:source "RCP-Base";
  Base:version "1.0";

  Base:baseType "Service" {
     Base:source "RCP-Base";
     Base:version "1.0";
  }

  organization "Rakuten";
  contact "";
  description "K8_Service generated from puml";

  revision 2020-08-20 {
    description "Initial Version";
    reference "";
  }

  container attributes {
    description "K8_Service Attributes";
    leaf k8sType {
      type string;
      description "";
      mandatory  "false";
      default "";
    }
    leaf k8sServiceClusterIP {
      type string;
      description "";
      mandatory  "false";
      default "";
    }
    leaf k8sAppname {
      type string;
      description "";
      mandatory  "false";
      default "";
    }
    leaf k8sTenant {
      type string;
      description "";
      mandatory  "false";
      default "";
    }
    leaf k8sTenantId {
      type string;
      description "";
      mandatory  "false";
      default "";
    }
    }

    container relationships {
    description "Relationship definitions";
    leaf contains_0 {
      type Base:relatedType { 
        Base:relationship "contains";
        Base:relType "ServiceInterface";
        Base:source "RCP-Base";
        Base:version "1.0";
      }
    }

    }
  }
