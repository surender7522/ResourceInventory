module GeoLocation {
  
  namespace "http://rakuten.com/RCP/network";

  prefix "GeoLocation";

  import Base {
    prefix "Base";
  }

  Base:source "RCP-Base";
  Base:version "1.0";

  Base:baseType "Location" {
     Base:source "RCP-Base";
     Base:version "1.0";
  }

  organization "Rakuten";
  contact "";
  description "GeoLocation generated from puml";

  revision 2020-08-20 {
    description "Initial Version";
    reference "";
  }

  container attributes {
    description "GeoLocation Attributes";
    leaf locLatitude {
      type string;
      description "";
      mandatory  "false";
      default "";
    }
    leaf locLongitude {
      type string;
      description "";
      mandatory  "false";
      default "";
    }
    leaf locAddress {
      type string;
      description "";
      mandatory  "false";
      default "";
    }
    leaf locCode {
      type string;
      description "";
      mandatory  "false";
      default "";
    }
    leaf locPinCode {
      type string;
      description "";
      mandatory  "false";
      default "";
    }
    leaf locSubType {
      type string;
      description "";
      mandatory  "false";
      default "";
    }
    }

    container relationships {
    description "Relationship definitions";
    leaf locates_0 {
      type Base:relatedType { 
        Base:relationship "locates";
        Base:relType "GeoLocation";
        Base:source "RCP-Base";
        Base:version "1.0";
      }
    }
    leaf locates_1 {
      type Base:relatedType { 
        Base:relationship "locates";
        Base:relType "GeoSubLocation";
        Base:source "RCP-Base";
        Base:version "1.0";
      }
    }

    }
  }
