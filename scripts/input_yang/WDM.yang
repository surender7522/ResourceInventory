module WDM {
  
  namespace "http://rakuten.com/RCP/network";

  prefix "WDM";

  import Base {
    prefix "Base";
  }

  Base:source "RCP-Base";
  Base:version "1.0";

  Base:baseType "NetworkElement" {
     Base:source "RCP-Base";
     Base:version "1.0";
  }

  organization "Rakuten";
  contact "";
  description "WDM generated from puml";

  revision 2020-08-20 {
    description "Initial Version";
    reference "";
  }

  container attributes {
    description "WDM Attributes";
    }

    container relationships {
    description "Relationship definitions";

    }
  }
