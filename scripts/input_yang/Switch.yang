module Switch {
  
  namespace "http://rakuten.com/RCP/network";

  prefix "Switch";

  import Base {
    prefix "Base";
  }

  Base:source "RCP-Base";
  Base:version "1.0";

  Base:baseType "NetworkElement" {
     Base:source "RCP-Base";
     Base:version "1.0";
  }

  organization "Rakuten";
  contact "";
  description "Switch generated from puml";

  revision 2020-08-20 {
    description "Initial Version";
    reference "";
  }

  container attributes {
    description "Switch Attributes";
    leaf swUsedPorts {
      type string;
      description "";
      mandatory  "false";
      default "";
    }
    leaf swAvailablePorts {
      type string;
      description "";
      mandatory  "false";
      default "";
    }
    leaf swEMSip {
      type string;
      description "";
      mandatory  "false";
      default "";
    }
    leaf swEMSVersion {
      type string;
      description "";
      mandatory  "false";
      default "";
    }
    }

    container relationships {
    description "Relationship definitions";

    }
  }
