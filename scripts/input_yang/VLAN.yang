module VLAN {
  
  namespace "http://rakuten.com/RCP/network";

  prefix "VLAN";

  import Base {
    prefix "Base";
  }

  Base:source "RCP-Base";
  Base:version "1.0";

  Base:baseType "LogicalResource" {
     Base:source "RCP-Base";
     Base:version "1.0";
  }

  organization "Rakuten";
  contact "";
  description "VLAN generated from puml";

  revision 2020-08-20 {
    description "Initial Version";
    reference "";
  }

  container attributes {
    description "VLAN Attributes";
    leaf vlanId {
      type string;
      description "";
      mandatory  "false";
      default "";
    }
    }

    container relationships {
    description "Relationship definitions";
    leaf contains_0 {
      type Base:relatedType { 
        Base:relationship "contains";
        Base:relType "VLANInterface";
        Base:source "RCP-Base";
        Base:version "1.0";
      }
    }

    }
  }
