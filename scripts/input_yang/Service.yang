module Service {
  
  namespace "http://rakuten.com/RCP/network";

  prefix "Service";

  import Base {
    prefix "Base";
  }

  Base:source "RCP-Base";
  Base:version "1.0";

  Base:baseType "Entity" {
     Base:source "RCP-Base";
     Base:version "1.0";
  }

  organization "Rakuten";
  contact "";
  description "Service generated from puml";

  revision 2020-08-20 {
    description "Initial Version";
    reference "";
  }

  container attributes {
    description "Service Attributes";
    }

    container relationships {
    description "Relationship definitions";

    }
  }
